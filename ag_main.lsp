(load "./Aguia/ag_base.lsp")
(load "./Aguia/ag_count.lsp")
(load "./Aguia/ag_dump.lsp")
(load "./Aguia/ag_pla.lsp")
(load "./Aguia/ag_psla.lsp")
(load "./Aguia/ag_pdla.lsp")
(load "./Aguia/ag_pra.lsp")
(load "./Aguia/ag_psrm.lsp")
(load "./Aguia/ag_pdrm.lsp")

(princ
    (strcat
        "\n:: \\U+00A9 Aguia Sistemas | Version 0.5 | Hemerson Camargo | "
        (menucmd "m=$(edtime,0,yyyy)")
        " ::"
    )
)

(princ)
